;;; ASG_Setup.lsp  -  ASG CAD Master Standard R1
;;; Saeed Al Siraj Glass & Aluminium Works L.L.C.  |  Al Siraj Group
;;;
;;; GENERATED by 08_Automation_Source/build_all.py from asg_standard.py.
;;; Do not edit by hand - change asg_standard.py and rebuild.
;;;
;;; Commands (all idempotent - re-running updates, never duplicates):
;;;   ASG-SETUP        table styles + named page setups + drawing variables,
;;;                    then ASG-QA.  Run once in ASG_Master_Template before
;;;                    SAVEAS DWG / DWT.
;;;   ASG-QA           read-only check of the whole standard inside AutoCAD;
;;;                    prints PASS / FAIL lines and writes ASG_QA_Log.txt
;;;                    next to the drawing.
;;;   ASG-PROFILE      OPTIONAL: user-profile (registry) settings. Asks first.
;;;
;;; Status: written without access to AutoCAD - ASG-QA is the verification.

(vl-load-com)

(defun asg:doc () (vla-get-ActiveDocument (vlax-get-acad-object)))

(defun asg:item (coll name / r)
  (setq r (vl-catch-all-apply 'vla-Item (list coll name)))
  (if (vl-catch-all-error-p r) nil r))

(setq asg:warn 0 asg:wlines nil)
(defun asg:ok (r) (not (vl-catch-all-error-p r)))
(defun asg:warnmsg (label err / s)
  (setq asg:warn (1+ asg:warn)
        s (strcat "WARN  " label " -> " (if err (vl-catch-all-error-message err) "failed"))
        asg:wlines (cons s asg:wlines))
  (princ (strcat "\n  " s)))

;; run (fn . args) protected: returns the result (T for nil results) or nil + WARN
(defun asg:try (label fn args / r)
  (setq r (vl-catch-all-apply fn args))
  (if (vl-catch-all-error-p r)
    (progn (asg:warnmsg label r) nil)
    (if r r T)))

;; AcCmColor: 0 = ByBlock (via ColorMethod), otherwise ACI
(defun asg:color (aci / c)
  (setq c (vl-catch-all-apply 'vla-GetInterfaceObject
            (list (vlax-get-acad-object) (strcat "AutoCAD.AcCmColor." (substr (getvar "ACADVER") 1 2)))))
  (cond ((vl-catch-all-error-p c) nil)
        ((= aci 0) (if (asg:ok (vl-catch-all-apply 'vla-put-ColorMethod (list c 193))) c nil))
        (T (if (asg:ok (vl-catch-all-apply 'vla-put-ColorIndex (list c aci))) c nil))))

;; ---------------------------------------------------------------- tables
;; row types: 1 data, 2 title, 4 header | align: 1 TL, 4 ML, 5 MC
;; Each property: legacy row-type API first, then the cell-style API
;; (AutoCAD 2008+, cell styles _TITLE / _HEADER / _DATA). Failures -> WARN, never abort.
(defun asg:cellstyles (rows / l)
  (if (= 1 (logand rows 1)) (setq l (cons "_DATA" l)))
  (if (= 4 (logand rows 4)) (setq l (cons "_HEADER" l)))
  (if (= 2 (logand rows 2)) (setq l (cons "_TITLE" l)))
  l)

(defun asg:rowprop (ts label fn fn2 rows val / r)
  (setq r (vl-catch-all-apply fn (list ts rows val)))
  (cond ((asg:ok r) T)
        ((and fn2 (vl-every '(lambda (cs) (asg:ok (vl-catch-all-apply fn2 (list ts cs val))))
                            (asg:cellstyles rows)))
         T)
        (T (asg:warnmsg label r) nil)))

(defun asg:gridlw (ts label grid rows lw / r ok)
  (setq r (vl-catch-all-apply 'vla-SetGridLineWeight (list ts grid rows lw)))
  (if (asg:ok r)
    T
    (progn
      (setq ok T)
      (foreach g '(1 2 4 8 16 32)
        (if (= g (logand grid g))
          (if (not (or (asg:ok (vl-catch-all-apply 'vla-SetGridLineWeight (list ts g rows lw)))
                       (vl-every '(lambda (cs) (asg:ok (vl-catch-all-apply 'vla-SetGridLineWeight2 (list ts cs g lw))))
                                 (asg:cellstyles rows))))
            (setq ok nil))))
      (if (not ok) (asg:warnmsg label r))
      ok)))

(defun asg:ts (name desc tH tA hH hA dH dA tSup hSup / dict ts c)
  (setq dict (asg:try "open ACAD_TABLESTYLE dictionary" 'vla-Item
               (list (vla-get-Dictionaries (asg:doc)) "ACAD_TABLESTYLE")))
  (if (= (type dict) 'VLA-OBJECT)
    (or (setq ts (asg:item dict name))
        (setq ts (asg:try (strcat name ": create") 'vla-AddObject (list dict name "AcDbTableStyle")))))
  (if (= (type ts) 'VLA-OBJECT)
    (progn
      (asg:try (strcat name ": description") 'vla-put-Description (list ts desc))
      (asg:try (strcat name ": flow direction") 'vla-put-FlowDirection (list ts 0))
      (asg:try (strcat name ": horizontal cell margin") 'vla-put-HorzCellMargin (list ts 1.5))
      (asg:try (strcat name ": vertical cell margin") 'vla-put-VertCellMargin (list ts 1.0))
      (asg:try (strcat name ": title row on/off") 'vla-put-TitleSuppressed (list ts (if tSup :vlax-true :vlax-false)))
      (asg:try (strcat name ": header row on/off") 'vla-put-HeaderSuppressed (list ts (if hSup :vlax-true :vlax-false)))
      (asg:rowprop ts (strcat name ": text style") 'vla-SetTextStyle 'vla-SetTextStyle2 7 "ASG-TEXT-SHEET")
      (asg:rowprop ts (strcat name ": title height") 'vla-SetTextHeight 'vla-SetTextHeight2 2 tH)
      (asg:rowprop ts (strcat name ": header height") 'vla-SetTextHeight 'vla-SetTextHeight2 4 hH)
      (asg:rowprop ts (strcat name ": data height") 'vla-SetTextHeight 'vla-SetTextHeight2 1 dH)
      (asg:rowprop ts (strcat name ": title alignment") 'vla-SetAlignment 'vla-SetAlignment2 2 tA)
      (asg:rowprop ts (strcat name ": header alignment") 'vla-SetAlignment 'vla-SetAlignment2 4 hA)
      (asg:rowprop ts (strcat name ": data alignment") 'vla-SetAlignment 'vla-SetAlignment2 1 dA)
      (if (setq c (asg:color 0))
        (asg:rowprop ts (strcat name ": text colour ByBlock") 'vla-SetColor 'vla-SetColor2 7 c))
      (asg:rowprop ts (strcat name ": no fill title/data") 'vla-SetBackgroundColorNone nil 3 :vlax-true)
      (asg:rowprop ts (strcat name ": header fill on") 'vla-SetBackgroundColorNone nil 4 :vlax-false)
      (if (setq c (asg:color 254))
        (asg:rowprop ts (strcat name ": header fill grey") 'vla-SetBackgroundColor 'vla-SetBackgroundColor2 4 c))
      (asg:gridlw ts (strcat name ": inside grid 0.18") 18 7 18)
      (asg:gridlw ts (strcat name ": outline 0.35") 45 7 35)
      (princ (strcat "\n  table style " name " done")))
    (princ (strcat "\n  table style " name " NOT created - see WARN above"))))

;; ---------------------------------------------------------- page setups
(defun asg:pagesetups (/ pcs name pc)
  (setq pcs (asg:try "open page setups" 'vla-get-PlotConfigurations (list (asg:doc))))
  (if (= (type pcs) 'VLA-OBJECT)
    (vlax-for lay (vla-get-Layouts (asg:doc))
      (if (= (vla-get-ModelType lay) :vlax-false)
        (progn
          (setq name (strcat "ASG-" (vla-get-Name lay)))
          (or (setq pc (asg:item pcs name))
              (setq pc (asg:try (strcat name ": create") 'vla-Add (list pcs name :vlax-false))))
          (if (and (= (type pc) 'VLA-OBJECT)
                   (asg:try (strcat name ": copy from layout") 'vla-CopyFrom (list pc lay)))
            (princ (strcat "\n  page setup " name " ok"))))))))

;; ------------------------------------------------------------------ QA
(setq asg:pass 0 asg:fail 0 asg:lines nil)
;; Full template = ASG_Master_Template.*; single-size templates and project
;; drawings legitimately miss some layouts / title blocks -> INFO, not FAIL.
(defun asg:master () (wcmatch (strcase (getvar "DWGNAME")) "ASG_MASTER_TEMPLATE*"))
(defun asg:out (s) (princ (strcat "\n" s)) (setq asg:lines (cons s asg:lines)))
(defun asg:chk (label ok)
  (if ok (setq asg:pass (1+ asg:pass)) (setq asg:fail (1+ asg:fail)))
  (asg:out (strcat (if ok "PASS  " "FAIL  ") label))
  ok)
(defun asg:missing (label)
  (if (asg:master)
    (asg:chk (strcat label " - MISSING") nil)
    (asg:out (strcat "INFO  " label " - not in this drawing"))))
(defun asg:same (a b)
  (cond ((and (numberp a) (numberp b)) (equal (float a) (float b) 1e-6))
        ((and (= (type a) 'STR) (= (type b) 'STR)) (= (strcase a) (strcase b)))
        (T (equal a b))))
(defun asg:var (name val)
  (asg:chk (strcat "variable " name " = " (vl-princ-to-string val)) (asg:same (getvar name) val)))
(defun asg:dv (e code def / a) (if (setq a (assoc code e)) (cdr a) def))
(defun asg:anno (ename) (and (assoc -3 (entget ename '("AcadAnnotative"))) T))
(defun asg:uniq (l / r) (foreach x l (if (not (member x r)) (setq r (cons x r)))) r)

(defun asg:layer (name aci lt lw plot / o e)
  (if (setq o (tblobjname "LAYER" name))
    (progn
      (setq e (entget o))
      (asg:chk (strcat "layer " name)
        (and (= (abs (cdr (assoc 62 e))) aci)
             (asg:same (cdr (assoc 6 e)) lt)
             (= (asg:dv e 370 -3) lw)
             (= (asg:dv e 290 1) plot))))
    (asg:chk (strcat "layer " name " - MISSING") nil)))

(defun asg:tstyle (name font anno / o e)
  (if (setq o (tblobjname "STYLE" name))
    (progn
      (setq e (entget o))
      (asg:chk (strcat "text style " name)
        (and (asg:same (cdr (assoc 3 e)) font)
             (equal (cdr (assoc 40 e)) 0.0 1e-9)
             (eq (asg:anno o) anno))))
    (asg:chk (strcat "text style " name " - MISSING") nil)))

(defun asg:dstyle (name dec adec anno / o e)
  (if (setq o (tblobjname "DIMSTYLE" name))
    (progn
      (setq e (entget o))
      (asg:chk (strcat "dimension style " name)
        (and (= (asg:dv e 271 4) dec)                 ; DIMDEC
             (= (asg:dv e 179 0) adec)                ; DIMADEC
             (equal (asg:dv e 140 0.18) 2.5 1e-9)     ; DIMTXT
             (equal (asg:dv e 41 0.18) 2.5 1e-9)      ; DIMASZ
             (equal (asg:dv e 144 1.0) 1.0 1e-9)      ; DIMLFAC - true measurement
             (eq (asg:anno o) anno))))
    (asg:chk (strcat "dimension style " name " - MISSING") nil)))

(defun asg:mlstyle (name anno / d e)
  (setq d (cdr (assoc -1 (dictsearch (namedobjdict) "ACAD_MLEADERSTYLE"))))
  (if (setq e (dictsearch d name))
    (asg:chk (strcat "multileader style " name " (annotative " (if anno "yes" "no") ")")
             (= (asg:dv e 296 0) (if anno 1 0)))
    (asg:chk (strcat "multileader style " name " - MISSING") nil)))

(defun asg:tblstyle (name / d)
  (setq d (cdr (assoc -1 (dictsearch (namedobjdict) "ACAD_TABLESTYLE"))))
  (asg:chk (strcat "table style " name) (and d (dictsearch d name))))

(defun asg:scales (want / names)
  (foreach p (dictsearch (namedobjdict) "ACAD_SCALELIST")
    (if (= (car p) 350) (setq names (cons (cdr (assoc 300 (entget (cdr p)))) names))))
  (foreach s want (asg:chk (strcat "annotation scale " s) (member s names)))
  (asg:chk (strcat "annotation scale list: " (itoa (length names)) " entries, no duplicates")
           (= (length names) (length (asg:uniq names)))))

(defun asg:get (fn obj / r) (setq r (vl-catch-all-apply fn (list obj))) (if (asg:ok r) r nil))
(defun asg:list (fn obj / r)
  (setq r (vl-catch-all-apply '(lambda () (vlax-safearray->list (vlax-variant-value (apply fn (list obj)))))))
  (if (asg:ok r) r nil))

(defun asg:layout (name media ctb / lay names num den std)
  (if (setq lay (asg:item (vla-get-Layouts (asg:doc)) name))
    (progn
      (vl-catch-all-apply 'vla-RefreshPlotDeviceInfo (list lay))
      (asg:chk (strcat name ": plot device DWG To PDF.pc3")
               (asg:same (asg:get 'vla-get-ConfigName lay) "DWG To PDF.pc3"))
      (setq names (asg:list 'vla-GetCanonicalMediaNames lay))
      (asg:chk (strcat name ": paper " media " exists on device and is selected")
               (and (member media names) (asg:same (asg:get 'vla-get-CanonicalMediaName lay) media)))
      (asg:chk (strcat name ": plot area = Layout") (equal (asg:get 'vla-get-PlotType lay) 5))
      (vl-catch-all-apply 'vla-GetCustomScale (list lay 'num 'den))
      (setq std (and (equal (asg:get 'vla-get-UseStandardScale lay) :vlax-true)
                     (equal (asg:get 'vla-get-StandardScale lay) 16)))
      (asg:chk (strcat name ": plot scale 1:1")
               (or std (and (numberp num) (numberp den) (/= den 0) (equal (/ (float num) den) 1.0 1e-9))))
      (asg:chk (strcat name ": plot style table " ctb) (asg:same (asg:get 'vla-get-StyleSheet lay) ctb))
      (setq names (asg:list 'vla-GetPlotStyleTableNames lay))
      (asg:chk (strcat name ": " ctb " installed in Plot Styles folder")
               (vl-some '(lambda (x) (asg:same x ctb)) names))
      (asg:chk (strcat name ": plot object lineweights on, not scaled")
               (and (equal (asg:get 'vla-get-PlotWithLineweights lay) :vlax-true)
                    (equal (asg:get 'vla-get-ScaleLineweights lay) :vlax-false)))
      (asg:chk (strcat name ": viewport borders not plotted")
               (equal (asg:get 'vla-get-PlotViewportBorders lay) :vlax-false)))
    (asg:missing (strcat "layout " name))))

(defun asg:tbattrs (blk tags / e found)
  (if (setq e (tblobjname "BLOCK" blk))
    (progn
      (while (setq e (entnext e))
        (if (= (cdr (assoc 0 (entget e))) "ATTDEF")
          (setq found (cons (strcase (cdr (assoc 2 (entget e)))) found))))
      (asg:chk (strcat "title block " blk ": " (itoa (length tags)) " attributes")
               (and (= (length found) (length tags))
                    (vl-every '(lambda (tg) (member tg found)) tags))))
    (asg:missing (strcat "title block " blk))))

(defun asg:noxrefs (/ b ok)
  (setq ok T b (tblnext "BLOCK" T))
  (while b
    (if (= 4 (logand 4 (cdr (assoc 70 b)))) (setq ok nil))
    (setq b (tblnext "BLOCK")))
  (asg:chk "no external references" ok))

(defun asg:writelog (/ fn f)
  (setq fn (strcat (getvar "DWGPREFIX") "ASG_QA_Log.txt")
        f (vl-catch-all-apply 'open (list fn "w")))
  (if (and f (asg:ok f))
    (progn
      (if asg:wlines
        (progn
          (write-line (strcat "ASG-SETUP warnings: " (itoa (length asg:wlines))) f)
          (foreach l (reverse asg:wlines) (write-line l f))
          (write-line "" f)))
      (foreach l (reverse asg:lines) (write-line l f))
      (close f)
      (princ (strcat "\nQA log written: " fn)))
    (princ "\nQA log could not be written (folder read-only).")))

(defun asg:tablestyles ()
  (asg:ts "ASG-TABLE-STANDARD" "Standard technical tables" 3.5 5 2.5 5 2.5 4 nil nil)
  (asg:ts "ASG-TABLE-MATERIAL" "Material schedules" 3.5 5 2.0 5 2.0 4 nil nil)
  (asg:ts "ASG-TABLE-GLASS" "Glass schedules" 3.5 5 2.0 5 2.0 4 nil nil)
  (asg:ts "ASG-TABLE-HARDWARE" "Hardware schedules" 3.5 5 2.0 5 2.0 4 nil nil)
  (asg:ts "ASG-TABLE-REVISION" "Revision registers" 3.5 5 2.0 5 2.0 4 T nil)
  (asg:ts "ASG-TABLE-REGISTER" "Drawing registers" 3.5 5 2.5 5 2.5 4 nil nil)
  (asg:ts "ASG-TABLE-NOTES" "General notes" 3.5 4 2.5 4 2.5 1 nil T)
  (princ))

(defun asg:setvars (/ r)
  (foreach p '(("CANNOSCALE" . "1:1") ("MSLTSCALE" . 1) ("ANNOALLVISIBLE" . 0) ("CMLEADERSTYLE" . "ASG-ML-ANNO") ("CTABLESTYLE" . "ASG-TABLE-STANDARD") ("HPLAYER" . "ASG-HATCH") ("DIMLAYER" . "ASG-DIMENSION") ("UCSFOLLOW" . 0))
    (setq r (vl-catch-all-apply 'setvar (list (car p) (cdr p))))
    (princ (strcat "\n  " (car p) (if (vl-catch-all-error-p r) " NOT SET (not supported in this release)" " set"))))
  (princ))

(defun asg:qa-body ()
  (asg:out "ASG-QA  -  ASG CAD Master Standard R1  -  read-only check")
  (asg:out (strcat "Drawing: " (getvar "DWGPREFIX") (getvar "DWGNAME")))
  (if (not (asg:master)) (asg:out "NOTE  Not the master template: ASG-QA checks TEMPLATE settings. In a project drawing FAIL on current layer / style / scale / model space is normal."))
  ;; units and drawing variables
  (asg:var "INSUNITS" 4)
  (asg:var "MEASUREMENT" 1)
  (asg:var "LUNITS" 2)
  (asg:var "LUPREC" 0)
  (asg:var "AUNITS" 0)
  (asg:var "AUPREC" 2)
  (asg:var "ANGBASE" 0.0)
  (asg:var "ANGDIR" 0)
  (asg:var "LIMCHECK" 0)
  (asg:var "LTSCALE" 1.0)
  (asg:var "PSLTSCALE" 1)
  (asg:var "CELTSCALE" 1.0)
  (asg:var "LWDISPLAY" 1)
  (asg:var "CELWEIGHT" -1)
  (asg:var "CECOLOR" "BYLAYER")
  (asg:var "DIMASSOC" 2)
  (asg:var "PLINEGEN" 1)
  (asg:var "FILLMODE" 1)
  (asg:var "MIRRTEXT" 0)
  (asg:var "TEXTSIZE" 2.5)
  (asg:var "PSTYLEMODE" 1)
  (asg:var "WORLDVIEW" 1)
  (asg:var "VISRETAIN" 1)
  (asg:var "PROXYGRAPHICS" 1)
  (asg:var "CLAYER" "ASG-OUTLINE-PRIMARY")
  (asg:var "TEXTSTYLE" "ASG-TEXT-ANNO")
  (asg:var "DIMSTYLE" "ASG-DIM-ANNO")
  (asg:var "CMLSTYLE" "ASG-MLINE-2")
  (asg:var "CANNOSCALE" "1:1")
  (asg:var "MSLTSCALE" 1)
  (asg:var "ANNOALLVISIBLE" 0)
  (asg:var "CMLEADERSTYLE" "ASG-ML-ANNO")
  (asg:var "CTABLESTYLE" "ASG-TABLE-STANDARD")
  (asg:var "HPLAYER" "ASG-HATCH")
  (asg:var "DIMLAYER" "ASG-DIMENSION")
  (asg:var "UCSFOLLOW" 0)
  ;; current dimension variables = ASG-DIM-ANNO (no style overrides)
  (asg:var "DIMTXSTY" "ASG-TEXT-ANNO")
  (asg:var "DIMTXT" 2.5)
  (asg:var "DIMASZ" 2.5)
  (asg:var "DIMDEC" 0)
  (asg:var "DIMEXO" 1.5)
  (asg:var "DIMEXE" 1.25)
  (asg:var "DIMGAP" 1.0)
  (asg:var "DIMTAD" 1)
  (asg:var "DIMLFAC" 1.0)
  ;; linetypes
  (asg:chk "linetype HIDDEN loaded" (tblsearch "LTYPE" "HIDDEN"))
  (asg:chk "linetype HIDDEN2 loaded" (tblsearch "LTYPE" "HIDDEN2"))
  (asg:chk "linetype CENTER loaded" (tblsearch "LTYPE" "CENTER"))
  (asg:chk "linetype CENTER2 loaded" (tblsearch "LTYPE" "CENTER2"))
  (asg:chk "linetype DASHED loaded" (tblsearch "LTYPE" "DASHED"))
  (asg:chk "linetype DASHED2 loaded" (tblsearch "LTYPE" "DASHED2"))
  (asg:chk "linetype DASHDOT loaded" (tblsearch "LTYPE" "DASHDOT"))
  (asg:chk "linetype DASHDOT2 loaded" (tblsearch "LTYPE" "DASHDOT2"))
  (asg:chk "linetype PHANTOM loaded" (tblsearch "LTYPE" "PHANTOM"))
  (asg:chk "linetype PHANTOM2 loaded" (tblsearch "LTYPE" "PHANTOM2"))
  (asg:chk "linetype DOT loaded" (tblsearch "LTYPE" "DOT"))
  ;; layers: colour, linetype, lineweight, plot flag
  (asg:layer "ASG-OUTLINE-PRIMARY" 7 "Continuous" 35 1)
  (asg:layer "ASG-OUTLINE-SECONDARY" 8 "Continuous" 18 1)
  (asg:layer "ASG-ALUMINIUM-PROFILE" 7 "Continuous" 25 1)
  (asg:layer "ASG-GLASS" 4 "Continuous" 18 1)
  (asg:layer "ASG-STAINLESS-STEEL" 7 "Continuous" 25 1)
  (asg:layer "ASG-MILD-STEEL" 7 "Continuous" 25 1)
  (asg:layer "ASG-HARDWARE" 8 "Continuous" 18 1)
  (asg:layer "ASG-FIXING" 8 "Continuous" 18 1)
  (asg:layer "ASG-GASKET" 8 "Continuous" 13 1)
  (asg:layer "ASG-SEALANT" 8 "Continuous" 13 1)
  (asg:layer "ASG-INSULATION" 252 "Continuous" 13 1)
  (asg:layer "ASG-CLADDING" 7 "Continuous" 25 1)
  (asg:layer "ASG-HIDDEN" 8 "HIDDEN2" 18 1)
  (asg:layer "ASG-CENTERLINE" 8 "CENTER2" 13 1)
  (asg:layer "ASG-CUTTING-PLANE" 7 "PHANTOM2" 35 1)
  (asg:layer "ASG-SECTION-CUT" 7 "Continuous" 50 1)
  (asg:layer "ASG-HATCH" 252 "Continuous" 9 1)
  (asg:layer "ASG-HATCH-FILL" 251 "Continuous" 9 1)
  (asg:layer "ASG-SETOUT" 8 "DASHDOT2" 13 1)
  (asg:layer "ASG-REFERENCE" 253 "Continuous" 13 1)
  (asg:layer "ASG-CONSTRUCTION" 6 "Continuous" 0 0)
  (asg:layer "ASG-DIMENSION" 3 "Continuous" 13 1)
  (asg:layer "ASG-TEXT" 7 "Continuous" 18 1)
  (asg:layer "ASG-TEXT-NOTE" 7 "Continuous" 18 1)
  (asg:layer "ASG-MULTILEADER" 3 "Continuous" 13 1)
  (asg:layer "ASG-TABLE" 7 "Continuous" 18 1)
  (asg:layer "ASG-LEVEL" 3 "Continuous" 13 1)
  (asg:layer "ASG-GRID" 8 "CENTER" 13 1)
  (asg:layer "ASG-REVISION" 1 "Continuous" 25 1)
  (asg:layer "ASG-SYMBOL" 3 "Continuous" 25 1)
  (asg:layer "ASG-BORDER" 7 "Continuous" 50 1)
  (asg:layer "ASG-TITLEBLOCK" 7 "Continuous" 25 1)
  (asg:layer "ASG-VIEWPORT" 6 "Continuous" 0 0)
  (asg:layer "ASG-NOPLOT" 6 "Continuous" 0 0)
  ;; styles
  (asg:tstyle "ASG-TEXT-ANNO" "arial.ttf" T)
  (asg:tstyle "ASG-TEXT-NOTE" "arial.ttf" T)
  (asg:tstyle "ASG-TEXT-SMALL" "arial.ttf" T)
  (asg:tstyle "ASG-TEXT-TITLE" "arialbd.ttf" nil)
  (asg:tstyle "ASG-TEXT-HEADING" "arialbd.ttf" nil)
  (asg:tstyle "ASG-TEXT-SHEET" "arial.ttf" nil)
  (asg:dstyle "ASG-DIM-ANNO" 0 2 T)
  (asg:dstyle "ASG-DIM-FIXED" 0 2 nil)
  (asg:dstyle "ASG-DIM-DETAIL" 1 2 T)
  (asg:dstyle "ASG-DIM-ANGULAR" 0 2 T)
  (asg:dstyle "ASG-DIM-RADIUS" 0 2 T)
  (asg:dstyle "ASG-DIM-DIAMETER" 0 2 T)
  (asg:mlstyle "ASG-ML-ANNO" T)
  (asg:mlstyle "ASG-ML-NOTE" nil)
  (asg:mlstyle "ASG-ML-DETAIL" T)
  (asg:mlstyle "ASG-ML-REFERENCE" T)
  (asg:tblstyle "ASG-TABLE-STANDARD")
  (asg:tblstyle "ASG-TABLE-MATERIAL")
  (asg:tblstyle "ASG-TABLE-GLASS")
  (asg:tblstyle "ASG-TABLE-HARDWARE")
  (asg:tblstyle "ASG-TABLE-REVISION")
  (asg:tblstyle "ASG-TABLE-REGISTER")
  (asg:tblstyle "ASG-TABLE-NOTES")
  (asg:chk "multiline style ASG-MLINE-2" (dictsearch (cdr (assoc -1 (dictsearch (namedobjdict) "ACAD_MLINESTYLE"))) "ASG-MLINE-2"))
  (asg:scales '("1:1" "1:2" "1:5" "1:10" "1:20" "1:25" "1:50" "1:100"))
  ;; layouts and page setups
  (asg:layout "A4-LANDSCAPE" "ISO_full_bleed_A4_(297.00_x_210.00_MM)" "ASG_Monochrome.ctb")
  (if (asg:item (vla-get-Layouts (asg:doc)) "A4-LANDSCAPE") (asg:chk "named page setup ASG-A4-LANDSCAPE" (asg:item (vla-get-PlotConfigurations (asg:doc)) "ASG-A4-LANDSCAPE")))
  (asg:layout "A4-PORTRAIT" "ISO_full_bleed_A4_(210.00_x_297.00_MM)" "ASG_Monochrome.ctb")
  (if (asg:item (vla-get-Layouts (asg:doc)) "A4-PORTRAIT") (asg:chk "named page setup ASG-A4-PORTRAIT" (asg:item (vla-get-PlotConfigurations (asg:doc)) "ASG-A4-PORTRAIT")))
  (asg:layout "A3-LANDSCAPE" "ISO_full_bleed_A3_(420.00_x_297.00_MM)" "ASG_Monochrome.ctb")
  (if (asg:item (vla-get-Layouts (asg:doc)) "A3-LANDSCAPE") (asg:chk "named page setup ASG-A3-LANDSCAPE" (asg:item (vla-get-PlotConfigurations (asg:doc)) "ASG-A3-LANDSCAPE")))
  (asg:layout "A3-PORTRAIT" "ISO_full_bleed_A3_(297.00_x_420.00_MM)" "ASG_Monochrome.ctb")
  (if (asg:item (vla-get-Layouts (asg:doc)) "A3-PORTRAIT") (asg:chk "named page setup ASG-A3-PORTRAIT" (asg:item (vla-get-PlotConfigurations (asg:doc)) "ASG-A3-PORTRAIT")))
  (asg:layout "A1-LANDSCAPE" "ISO_full_bleed_A1_(841.00_x_594.00_MM)" "ASG_Monochrome.ctb")
  (if (asg:item (vla-get-Layouts (asg:doc)) "A1-LANDSCAPE") (asg:chk "named page setup ASG-A1-LANDSCAPE" (asg:item (vla-get-PlotConfigurations (asg:doc)) "ASG-A1-LANDSCAPE")))
  ;; title blocks
  (asg:tbattrs "ASG-TB-A4" '("PROJECT" "LOCATION" "CLIENT" "CONSULTANT" "DWG_TITLE" "DWG_TITLE_2" "DWG_NO" "REV" "DATE" "DRAWN_BY" "CHECKED_BY" "APPROVED_BY" "SCALE" "SHEET_NO" "DWG_STATUS"))
  (asg:tbattrs "ASG-TB-A3" '("PROJECT" "LOCATION" "CLIENT" "CONSULTANT" "DWG_TITLE" "DWG_TITLE_2" "DWG_NO" "REV" "DATE" "DRAWN_BY" "CHECKED_BY" "APPROVED_BY" "SCALE" "SHEET_NO" "DWG_STATUS"))
  (asg:tbattrs "ASG-TB-A1" '("PROJECT" "LOCATION" "CLIENT" "CONSULTANT" "DWG_TITLE" "DWG_TITLE_2" "DWG_NO" "REV" "DATE" "DRAWN_BY" "CHECKED_BY" "APPROVED_BY" "SCALE" "SHEET_NO" "DWG_STATUS"))
  ;; content
  (asg:chk "model space is empty" (null (ssget "_X" (list (cons 410 "Model")))))
  (asg:noxrefs)
  T)

(defun c:ASG-QA (/ r)
  (setq asg:pass 0 asg:fail 0 asg:lines nil)
  (setq r (vl-catch-all-apply 'asg:qa-body nil))
  (if (vl-catch-all-error-p r) (asg:chk (strcat "QA stopped early: " (vl-catch-all-error-message r)) nil))
  (asg:out (strcat "RESULT: " (itoa asg:pass) " PASS, " (itoa asg:fail) " FAIL"))
  (asg:writelog)
  (princ))

(defun c:ASG-PROFILE (/ r)
  (initget "Yes No")
  (if (= (getkword "\nChange YOUR AutoCAD profile (registry) settings to ASG defaults? [Yes/No] <No>: ") "Yes")
    (progn
      (foreach p '(("OSMODE" . 2223) ("AUTOSNAP" . 63) ("POLARANG" . 45.0) ("ORTHOMODE" . 0) ("DYNMODE" . 3) ("DYNPROMPT" . 1) ("SELECTIONCYCLING" . 2) ("GRIPS" . 1) ("GRIPSIZE" . 5) ("PICKBOX" . 4) ("APERTURE" . 8) ("PICKFIRST" . 1) ("PICKADD" . 2) ("ANNOAUTOSCALE" . 0) ("SAVETIME" . 10) ("ISAVEBAK" . 1) ("LAYOUTREGENCTL" . 2) ("REFPATHTYPE" . 1))
        (setq r (vl-catch-all-apply 'setvar (list (car p) (cdr p))))
        (princ (strcat "\n  " (car p) (if (vl-catch-all-error-p r) " not set" " set"))))
      (princ "\nASG profile settings applied."))
    (princ "\nNo changes made."))
  (princ))

(defun c:ASG-SETUP (/ r)
  (setq asg:warn 0 asg:wlines nil)
  (princ "\nASG-SETUP ---------------------------------------------")
  (foreach step '(("Table styles" . asg:tablestyles) ("Page setups" . asg:pagesetups)
                  ("Drawing variables" . asg:setvars))
    (princ (strcat "\n" (car step) ":"))
    (setq r (vl-catch-all-apply (cdr step) nil))
    (if (vl-catch-all-error-p r) (asg:warnmsg (car step) r)))
  (c:ASG-QA)
  (princ (strcat "\nASG-SETUP complete with " (itoa asg:warn) " warning(s)."
                 "\nIf RESULT shows 0 FAIL: SAVEAS DWG, then SAVEAS DWT."
                 "\nOtherwise send ASG_QA_Log.txt to the CAD in-charge."))
  (princ))

(princ "\nASG_Setup loaded: ASG-SETUP, ASG-QA, ASG-PROFILE (optional).")
(princ)
